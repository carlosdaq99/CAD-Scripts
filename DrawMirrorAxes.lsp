; DrawMirrorAxes.lsp
; Command: DrawMirrorAxes
; For each selected entity, draws a line between calculated mirror axis points (mirrorPt1 and mirrorPt2)
; Author: GitHub Copilot

(defun c:DrawMirrorAxes (/ ss curveEname curveVla objCount i objEname objVla objPt curvePt tangent mirrorPt1 mirrorPt2)
  (prompt "\nSelect the array of objects to visualize mirror axes: ")
  (setq ss (ssget))
  (if (null ss)
    (progn (prompt "\nNo objects selected.") (exit))
  )
  (prompt "\nSelect the curve to mirror along: ")
  (setq curveEname (car (entsel)))
  (if (null curveEname)
    (progn (prompt "\nNo curve selected.") (exit))
  )
  (setq curveVla (vlax-ename->vla-object curveEname))
  (setq objCount (sslength ss))
  (setq i 0)
  (while (< i objCount)
    (setq objEname (ssname ss i))
    (setq objVla (vlax-ename->vla-object objEname))
    ;; Try centroid, bounding box, etc. (same logic as main routine)
    (setq objPt nil)
    (if (vlax-method-applicable-p objVla 'GetCentroid)
      (setq objPt (vlax-invoke-method objVla 'GetCentroid))
    )
    (if (and (null objPt) (vlax-property-available-p objVla 'Centroid))
      (setq objPt (vlax-get objVla 'Centroid))
    )
    (if (and (null objPt) (acet-ent-geomextents objEname))
      (setq bbox (acet-ent-geomextents objEname)
            objPt (mapcar '(lambda (a b) (/ (+ a b) 2.0)) (car bbox) (cadr bbox)))
    )
    (if (null objPt)
      (cond
        ((= (cdr (assoc 0 (entget objEname))) "SPLINE")
          (setq objPt (cdr (assoc 11 (entget objEname))))
        )
        ((vlax-property-available-p objVla 'InsertionPoint)
          (setq objPt (vlax-get objVla 'InsertionPoint))
        )
        ((vlax-property-available-p objVla 'StartPoint)
          (setq objPt (vlax-get objVla 'StartPoint))
        )
        ((vlax-method-applicable-p objVla 'GetStartPoint)
          (setq objPt (vlax-invoke-method objVla 'GetStartPoint))
        )
        ((vlax-property-available-p objVla 'Coordinates)
          (setq objPt (vlax-get objVla 'Coordinates))
        )
      )
    )
    (if objPt
      (progn
        (setq curvePt (vlax-curve-getClosestPointTo curveVla objPt))
        (setq tangent (vlax-curve-getFirstDeriv curveVla (vlax-curve-getParamAtPoint curveVla curvePt)))
        (setq mirrorPt1 curvePt)
        ;; Normalize tangent and scale to 5 units (meters)
        (setq tangentLen (distance '(0 0 0) tangent))
        (if (> tangentLen 1e-8)
          (setq tangentDir (mapcar '(lambda (x) (/ x tangentLen)) tangent))
          (setq tangentDir '(1.0 0.0 0.0)) ; fallback direction if tangent is zero
        )
        (prompt (strcat "\n[DIAG] TangentDir: " (rtos (car tangentDir) 2 12) ", " (rtos (cadr tangentDir) 2 12) ", " (rtos (caddr tangentDir) 2 12)))
        (setq mirrorPt2 (mapcar '+ mirrorPt1 (mapcar '(lambda (x) (* x 5.0)) tangentDir)))
        (prompt (strcat "\n[DIAG] Drawing axis for entity: " (cdr (assoc 0 (entget objEname)))))
        (prompt (strcat "\n[DIAG] Axis point 1: " (rtos (car mirrorPt1) 2 12) ", " (rtos (cadr mirrorPt1) 2 12) ", " (rtos (caddr mirrorPt1) 2 12)))
        (prompt (strcat "\n[DIAG] Axis point 2: " (rtos (car mirrorPt2) 2 12) ", " (rtos (cadr mirrorPt2) 2 12) ", " (rtos (caddr mirrorPt2) 2 12)))
        (setq axisLen (distance mirrorPt1 mirrorPt2))
        (prompt (strcat "\n[DIAG] Axis length: " (rtos axisLen 2 12)))
        (if (> axisLen 1e-6)
          (command "_.LINE" mirrorPt1 mirrorPt2 "")
          (prompt "\n[DIAG] Axis too short, not drawing line.")
        )
      )
    )
    (setq i (1+ i))
  )
  (princ "\nDrawMirrorAxes complete.")
)

(princ "\nDrawMirrorAxes.lsp loaded. Type DrawMirrorAxes to run.\n")
