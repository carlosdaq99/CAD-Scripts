;;----------------------=={ Password Generator }==----------------------;;
;;                                                                      ;;
;;  This novelty program will generate a pseudo-random password string  ;;
;;  based on the parameters specified.                                  ;;
;;                                                                      ;;
;;  Upon issuing the command 'password' at the command-line, the user   ;;
;;  is presented with a dialog interface providing several options to   ;;
;;  control the length & content of the generated password.             ;;
;;                                                                      ;;
;;  The user may specify a password length of between 1 and 99          ;;
;;  characters, control whether symbols, numbers, lower-case and/or     ;;
;;  upper-case characters are permitted in the password, and also       ;;
;;  whether visually similar characters (such as 1,l,I,O,0) should be   ;;
;;  excluded.                                                           ;;
;;                                                                      ;;
;;  The password generated by the program may be subsequently copied    ;;
;;  to the clipboard by pressing the 'Copy' button.                     ;;
;;                                                                      ;;
;;----------------------------------------------------------------------;;
;;  Author:  Lee Mac, Copyright © 2013  -  www.lee-mac.com              ;;
;;----------------------------------------------------------------------;;

(defun c:password ( / *error* bit dch dcl des key len rtn )

    ;; Program Defaults
    (setq len 10
          bit (+ 4 8 16)
    )

    (defun *error* ( msg )
        (if (= 'file (type des))
            (close des)
        )
        (if (and (= 'int (type dch)) (< 0 dch))
            (unload_dialog dch)
        )
        (if (and (= 'str (type dcl)) (findfile dcl))
            (vl-file-delete dcl)
        )
        (if (and msg (not (wcmatch (strcase msg t) "*break,*cancel*,*exit*")))
            (princ (strcat "\nError: " msg))
        )
        (princ)
    )

    (if
        (and
            (setq dcl (vl-filename-mktemp nil nil ".dcl"))
            (setq des (open dcl "w"))
            (foreach x
               '(
                    "pass : dialog"
                    "{"
                    "    key = \"dcl\";"
                    "    spacer;"
                    "    : boxed_column"
                    "    {"
                    "        label = \"Parameters\";"
                    "        spacer;"
                    "        : row"
                    "        {"
                    "            alignment = left;"
                    "            fixed_width = true;"
                    "            : edit_box"
                    "            {"
                    "                key = \"len\";"
                    "                edit_width = 2;"
                    "                edit_limit = 2;"
                    "                alignment = left;"
                    "                mnemonic = \"L\";"
                    "            }"
                    "            : text"
                    "            {"
                    "                label = \"Password &Length (1 - 99)\";"
                    "            }"
                    "        }"
                    "        spacer;"
                    "        : toggle { key = \"2\";  label = \"Include &Symbols (e.g. @, $, #)\";                  mnemonic = \"S\";} spacer;"
                    "        : toggle { key = \"4\";  label = \"Include L&owercase Letters (a - z)\";               mnemonic = \"o\";} spacer;"
                    "        : toggle { key = \"8\";  label = \"Include &Uppercase Letters (A - Z)\";               mnemonic = \"U\";} spacer;"
                    "        : toggle { key = \"16\"; label = \"Include &Numbers (0 - 9)\";                         mnemonic = \"N\";} spacer;"
                    "        : toggle { key = \"1\";  label = \"&Exclude Similar Characters (e.g. I, l, 1, O, 0)\"; mnemonic = \"E\";} spacer;"
                    "    }"
                    "    spacer;"
                    "    : button"
                    "    {"
                    "        key = \"gen\";"
                    "        label = \"&Generate Password\";"
                    "        fixed_width = true;"
                    "        alignment = centered;"
                    "        height = 2;"
                    "        mnemonic = \"G\";"
                    "    }"
                    "    spacer;"
                    "    : boxed_column"
                    "    {"
                    "        label = \"Password\";"
                    "        spacer;"
                    "        : row"
                    "        {"
                    "            : edit_box"
                    "            {"
                    "                key = \"rtn\";"
                    "                width = 40;"
                    "                fixed_width = true;"
                    "            }"
                    "            : button"
                    "            {"
                    "                key = \"cpy\";"
                    "                label = \"&Copy\";"
                    "                fixed_width = true;"
                    "                mnemonic = \"C\";"
                    "            }"
                    "        }"
                    "        spacer;"
                    "    }"
                    "    spacer;"
                    "    : button"
                    "    {"
                    "        key = \"accept\";"
                    "        label = \"E&xit\";"
                    "        is_default = true;"
                    "        is_cancel = true;"
                    "        fixed_width = true;"
                    "        alignment = centered;"
                    "        width = 15;"
                    "        mnemonic = \"x\";"
                    "    }"
                    "    spacer;"
                    "}"
                )
                (write-line x des)
            )
            (not (setq des (close des)))
            (< 0 (setq dch (load_dialog dcl)))
            (new_dialog "pass" dch)
        )
        (progn
            (mode_tile   "cpy"  1)
            (set_tile    "dcl" "Password Generator V1.0 by Lee Mac")
            (set_tile    "len"  (itoa len))
            (action_tile "len"
                (strcat
                    "(setq len (atoi $value))"
                    "(set_tile \"rtn\" \"\")"
                    "(mode_tile \"cpy\" 1)"
                )
            )
            (setq key 1)
            (repeat 5
                (set_tile    (itoa key) (if (= key (logand key bit)) "1" "0"))
                (action_tile (itoa key)
                    (strcat
                        "(setq bit (boole (if (= \"1\" $value) 7 4) " (itoa key) " bit))"
                        "(set_tile \"rtn\" \"\")"
                        "(mode_tile \"cpy\" 1)"
                        "(mapcar 'mode_tile '(\"gen\" \"rtn\") (if (< bit 2) '(1 1) '(0 0)))"
                    )
                )
                (setq key (lsh key 1))
            )
            (action_tile "gen"
                (vl-prin1-to-string
                   '(if (< len 1)
                        (progn
                            (set_tile  "rtn" "Please enter a password length between 1-99")
                            (mode_tile "rtn" 1)
                            (mode_tile "cpy" 1)
                            (mode_tile "len" 2)
                        )
                        (progn
                            (set_tile  "rtn" (setq rtn (password:generate len bit)))
                            (mode_tile "rtn" 0)
                            (mode_tile "cpy" 0)
                        )
                    )
                )
            )
            (action_tile "cpy"
                (strcat
                    "(if (= 'str (type rtn)) (password:copytoclipboard rtn))"
                    "(mode_tile \"cpy\" 1)"
                )
            )
            (start_dialog)
        )
        (princ "\nUnable to load password dialog.")
    )
    (*error* nil)
    (princ)
)

(defun password:generate ( len bit / lst rng rtn tmp )
    (setq tmp 2)
    (foreach itm
       '(
            (
                033 034 035 036 037 038 039 040
                041 042 043 044 045 046 047 058
                059 060 061 062 063 064 091 092
                093 094 095 096 123 124 125 126
            )
            (
                097 098 099 100 101 102 103 104
                105 106 107 108 109 110 111 112
                113 114 115 116 117 118 119 120
                121 122
            )
            (
                065 066 067 068 069 070 071 072
                073 074 075 076 077 078 079 080
                081 082 083 084 085 086 087 088
                089 090
            )
            (
                048 049 050 051 052 053 054 055
                056 057
            )
        )
        (if (= tmp (logand tmp bit))
            (setq lst (append lst itm))
        )
        (setq tmp (lsh tmp 1))
    )
    (if (= 1 (logand 1 bit))
        (setq lst (vl-remove-if '(lambda ( x ) (member x '(48 49 73 79 105 108 111))) lst))
    )
    (setq rng (1- (length lst)))
    (repeat len (setq rtn (cons (nth (LM:randrange 0 rng) lst) rtn)))
    (vl-list->string rtn)
)

;; Same method as MP demonstrates here: http://bit.ly/170kacW
(defun password:copytoclipboard ( str / clp htm par )
    (if (setq htm (vlax-create-object "htmlfile"))
        (progn
            (vl-catch-all-apply
               '(lambda ( )
                    (setq par (vlax-get htm 'parentwindow)
                          clp (vlax-get par 'clipboarddata)
                    )
                    (vlax-invoke clp 'setdata "Text" str)
                )
            )
            (foreach obj (list clp par htm)
                (if (= 'vla-object (type obj))
                    (vlax-release-object obj)
                )
            )
            str
        )
    )
)

;; Rand  -  Lee Mac
;; PRNG implementing a linear congruential generator with
;; parameters derived from the book 'Numerical Recipes'

(defun LM:rand ( / a c m )
    (setq m   4294967296.0
          a   1664525.0
          c   1013904223.0
          $xn (rem (+ c (* a (cond ($xn) ((getvar 'date))))) m)
    )
    (/ $xn m)
)

;; Random in Range  -  Lee Mac
;; Returns a pseudo-random integral number in a given range (inclusive)

(defun LM:randrange ( a b )
    (fix (+ a (* (LM:rand) (- b a -1))))
)

;;----------------------------------------------------------------------;;

(vl-load-com)
(princ
    (strcat
        "\n:: Password.lsp | Version 1.0 | \\U+00A9 Lee Mac "
        (menucmd "m=$(edtime,$(getvar,date),YYYY)")
        " www.lee-mac.com ::"
        "\n:: Type \"password\" to Invoke ::"
    )
)
(princ)

;;----------------------------------------------------------------------;;
;;                             End of File                              ;;
;;----------------------------------------------------------------------;;
